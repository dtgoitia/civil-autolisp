(defun c:xx ()
  ; UK coordinates: 453159.7,202458.0
  ; Google maps coordinates: 51.718337, -1.2318854

  ; UK: 0,0
  ; GM: 49.766809,-7.5571598

  ; UK: 100,100
  ; GM: 49.767770,-7.5558804

  ; UK: 1000,1000
  ; GM: 49.776425,-7.5443633

  ; COORDIANTE TRANSFORMATION FORMULAS:
  ; http://www.movable-type.co.uk/scripts/latlong-os-gridref.html

  ;https://www.gridreferencefinder.com/
  ;http://www.google.com/maps/place/49.46800006494457,17.11514008755796
  ;http://www.google.com/maps/place/51.718337,-1.2318854
)
