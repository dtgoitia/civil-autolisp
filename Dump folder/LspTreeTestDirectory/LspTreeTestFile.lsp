(defun c:TestFunction ()
  ; Command version of DT:TestFunction
  (DT:TestFunction)

  ; v0.0 - 2017.08.22 - First issue
  ; Author: David Torralba
  ; Last revision: 2017.08.22
)
(defun DT:TestFunction ()
  ; DT:TestFunction function description
  T

  ; v0.0 - 2017.08.22 - First issue
  ; Author: David Torralba
  ; Last revision: 2017.08.22
)
