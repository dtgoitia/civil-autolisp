(defun c:TestFunction2 ()
  ; Command version of DT:TestFunction2
  (DT:TestFunction2)
  (DT:TestFunction3)
  (DT:TestFunction4)

  ; v0.0 - 2017.08.22 - First issue
  ; Author: David Torralba
  ; Last revision: 2017.08.22
)
(defun DT:TestFunction2 ()
  ; DT:TestFunction2 function description
  (DT:TestFunction4)
  (DT:TestFunction44)
  T

  ; v0.0 - 2017.08.22 - First issue
  ; Author: David Torralba
  ; Last revision: 2017.08.22
)
(setvar "adasd" 2)
(defun c:xx ()
  (defun c:asdasd ()
    T
  )
  nil
)
