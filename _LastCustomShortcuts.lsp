; DO NOT REMOVE THIS LINE. It's a checking.
(defun c:1 () (princ "\nUpdate Manhole Schedule Diagram" )(c:UMSD) )
(defun c:2 () (princ "\nMSCS7" )(c:MSCS7) )
(defun c:3 () (princ "\nBY" )(c:By) )
(defun c:4 () (princ "\nUpdate Manhole Schedule Pipe Sizes" )(c:UMSP) )
