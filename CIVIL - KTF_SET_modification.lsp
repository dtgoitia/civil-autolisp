(DEFUN c:ktf_set ()
  (setq old_cmdecho (getvar "cmdecho"))
  (setvar "cmdecho" 0)
  (if (= sf nil) (progn
   (setq sf (getreal "\nNominal Scale   1:<500>  1:"))
   (if (= sf nil) (setq sf 500.0))
   (setq sf (/ sf 571.428557))
  ))

  (if (= cacc nil) (progn
   (setq cacc (getint "\nNumber of Decimal Places for display of Co-ordinates <3> : "))
   (if (= cacc nil) (setq cacc 3))
  ))

  (setq olay (getvar "clayer"))
  (setq lay (getstring (strcat "\nLayer for co-ordinate boxes to be drawn on (current layer) <" olay "> : ")))
  (if (= lay "") (setq lay olay))
  (command "_layer" "_m" lay "")

  (setq p 0)
  (princ "\nPick Polyline  [1 Polyline ONLY] :")
  (setq a (ssget)
        b (ssname a 0)
        con (entget b)
  )
  (if (= (cdr (assoc 0 con)) "LWPOLYLINE")
    (progn
      (setq counter 0)
      (repeat (length con)
        (setq a (nth counter con))
        (if (equal (car a) 10)
          (progn
            (setq pt1 (cdr a)
              X (RTOS (NTH 0 pt1) 2 3)
              Y (RTOS (NTH 1 pt1) 2 3)
              E  (STRCAT "E " (RTOS (NTH 0 pt1) 2 cacc))
              N  (STRCAT "N " (RTOS (NTH 1 pt1) 2 cacc))
            )
            (setvar "osmode" 0)
            (command "_insert" "XY_advanced" pt1 sf "" "" E N)
          )
        )
        (setq counter (+ counter 1))
      )
    )
  )
  (if (= (cdr (assoc 0 con)) "POLYLINE")
    (progn
      (setq b (entnext (cdr (assoc -1 con))))
      (while  (/= (cdr (assoc 0 (entget b))) "SEQEND")
        (setq con (entget b)
              pt1 (cdr (assoc 10 con))
              b (entnext (cdr (assoc -1 con)))
              X (RTOS (NTH 0 pt1) 2 3)
              Y (RTOS (NTH 1 pt1) 2 3)
              E  (STRCAT "E " (RTOS (NTH 0 pt1) 2 cacc))
              N  (STRCAT "N " (RTOS (NTH 1 pt1) 2 cacc))
        )
        (setvar "osmode" 0)
        (command "_insert" "XY_advanced" pt1 sf "" "" E N)
      )
    )
  )
  (princ)
  (setvar "osmode" old_osmode)
  (setvar "cmdecho" old_cmdecho)
  
  ; v0.0 - 2016.03.03
  ; Author: David Torralba
  ; Last revision: 2016.03.03
)
